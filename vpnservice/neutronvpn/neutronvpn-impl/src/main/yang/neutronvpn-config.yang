module neutronvpn-config {
    yang-version 1;
    namespace "urn:opendaylight:netvirt:neutronvpn:config";
    prefix "neutronvpn-config";
    
    description
        "Configuration for neutronvpn-impl.";

    revision "2016-08-06" {
        description
                "Initial revision.";
    }

    container neutronvpn-config {
        config true;
        leaf use-transport-zone {
            type boolean;
            default true;
        }
    }    
}
