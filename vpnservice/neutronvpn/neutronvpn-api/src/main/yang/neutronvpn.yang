module neutronvpn {

    namespace "urn:opendaylight:netvirt:neutronvpn";
    prefix neutronvpn;

    import ietf-yang-types { prefix yang; revision-date "2013-07-15";}

    revision "2015-06-02" {
        description "Neutron based L3Service Module, provides integration of ODL VPN service with Neutron NSF";
    }

    container subnetmaps{
        list subnetmap {
            key id;
            leaf id {
              type    yang:uuid;
              description "UUID representing the subnet ";
            }

            leaf subnet-ip {
                type    string;
                description "Specifies the subnet IP in CIDR format";
            }

            leaf tenant-id {
                type    yang:uuid;
                description "The UUID of the tenant that will own the subnet.";
            }

            leaf network-id {
              type    yang:uuid;
              description "UUID representing the network ";
            }

            leaf router-id {
              type    yang:uuid;
              description "router to which this subnet belongs";
            }

            leaf router-interface-name {
              type    yang:uuid;
              description "router interface on this subnet";
            }

            leaf router-intf-mac-address {
              type    string;
              description "router interface mac address on this subnet";
            }

            leaf-list router-interface-fixed-ips {
              type    string;
              description "fixed ip of the router interface on this subnet";
            }

            leaf vpn-id {
              type    yang:uuid;
              description "VPN to which this subnet belongs";
            }

            leaf-list port-list {
              type yang:uuid;
            }

            leaf-list direct-port-list{
              type yang:uuid;
            }
        }
    }

    container networkMaps{
        list networkMap {
            key network-id;

            leaf network-id {
                type    yang:uuid;
                description "UUID representing the network";
            }

            leaf-list subnet-id-list {
                type    yang:uuid;
                description "List of UUIDs representing the subnets associated to the network";
            }
        }
    }

    grouping vpn-instance{

        leaf id {
            mandatory "true";
            type    yang:uuid;
            description "vpn-id";
        }

        leaf name {
          type    string;
          description "VPN name";
        }

        leaf tenant-id {
            type    yang:uuid;
            description "The UUID of the tenant that will own the subnet.";
        }

        leaf-list route-distinguisher {
            type string;
            description
            "configures a route distinguisher (RD) for the VPN instance.
             Format is ASN:nn or IP-address:nn.";
        }

        leaf-list import-RT {
            type string;
            description
            "configures a list of import route target.
             Format is ASN:nn or IP-address:nn.";
        }

        leaf-list export-RT{
            type string;
            description
            "configures a list of export route targets.
             Format is ASN:nn or IP-address:nn.";
        }

        leaf router-id {
          type    yang:uuid;
          description "UUID of router ";
        }

        leaf-list network-ids {
          type    yang:uuid;
          description "UUID representing the network ";
        }
        leaf l3vni {
           type uint32;
        }

    }

    container vpnMaps {
        list vpnMap {
            key vpn-id;
            leaf vpn-id {
                type    yang:uuid;
                description "vpn-id";
            }
            leaf name {
                type  string;
                description "vpn name";
            }
            leaf tenant-id {
                type    yang:uuid;
                description "The UUID of the tenant that will own the subnet.";
            }

            leaf router-id {
              type    yang:uuid;
              description "UUID of router ";
            }
            leaf-list network_ids {
              type    yang:uuid;
              description "UUID representing the network ";
            }
        }
    }

    /* Data models to adhere to restart requirements */
    container neutron-vpn-portip-port-data {
        list vpn-portip-to-port {
            key "vpn-name port-fixedip";
            leaf vpn-name { type string;}
            leaf port-fixedip { type string;}
            leaf port-name { type string;}
            leaf mac-address { type string;}
            leaf subnet-ip { type boolean;}
            leaf config { type boolean;}
            leaf learnt { type boolean; }
        }
    }

    container router-interfaces-map {
        list router-interfaces {
            key router-id;
            leaf router-id { type yang:uuid; }
            list interfaces {
                key interface-id;
                leaf interface-id { type string; }
            }
        }
    }

    /* container for DHCP Configuration */
    container dhcp-config {
        list configs {
            leaf lease-duration {
                type    int32;
                description "default lease duration for dhcp lease.
                             -1 means infinite";
            }
            leaf default-domain {
                type string;
                description "default domain-name. used in dhcp reply";
            }
        }
    }

    rpc createL3VPN{
        description "Create one or more L3VPN(s)";
        input {
            list l3vpn {
                uses vpn-instance;
            }
        }
        output {
            leaf-list response {
                type    string;
                description "Status response for createVPN RPC";
            }
        }
    }

    rpc associateRouter {
        description "associates a router with L3VPN";
        input {
            leaf vpn-id {
                type    yang:uuid;
                mandatory "true";
                description "vpn-id";
            }
            leaf router-id {
                type    yang:uuid;
                mandatory "true";
                description "vpn-id";
            }
        }
    }

    rpc dissociateRouter {
        description "dissociates a router with L3VPN";
        input {
            leaf vpn-id {
                type    yang:uuid;
                mandatory "true";
                description "vpn-id";
            }
            leaf router-id {
                type    yang:uuid;
                mandatory "true";
                description "router-id";
            }
        }
    }

    rpc associateNetworks {
        description "associates a list of networks with L3VPN";
        input {
            leaf vpn-id {
                type    yang:uuid;
                mandatory "true";
                description "vpn-id";
            }
            leaf-list network-id {
                type    yang:uuid;
                description "network-id";
            }
        }
        output {
            leaf response {
                type    string;
                description "Status response for associateNetworks RPC";
            }
        }
    }

    rpc dissociateNetworks{
        description "dissociates a list of networks with L3VPN";
        input {
            leaf vpn-id {
                type    yang:uuid;
                mandatory "true";
                description "vpn-id";
            }
            leaf-list network-id {
                type    yang:uuid;
                description "network-id";
            }
        }
        output {
            leaf response {
                type    string;
                description "Status response for dissociateNetworks RPC";
            }
        }
    }

    rpc deleteL3VPN{
        description "delete VPNs for specified Id list";
        input {
            leaf-list id {
                type    yang:uuid;
                description "vpn-id";
            }
        }
        output {
            leaf-list response {
                type    string;
                description "Status response for deleteL3VPN RPC";
            }
        }
    }

    rpc getL3VPN{
        description "returns VPN configuration";
        input {
            leaf id {
                type    yang:uuid;
                description "vpn-id";
            }
        }
        output {
            list l3vpn-instances {
                uses vpn-instance;
            }
        }
    }

    rpc get-fixedIPs-for-neutron-port {
    description "returns neutron port fixed IPs";
        input {
            leaf port-id {
                type yang:uuid;
            }
        }
        output {
            leaf-list fixedIPs {
                type    string;
                description "The neutron port fixedIPs list corresponding to the port uuid";
            }
        }
    }

    notification subnet-added-to-vpn{
            description "new subnet added to vpn";
            leaf subnet-id {
                type yang:uuid;
            }
            leaf subnet-ip {
                type string;
            }
            leaf vpn-name {
                type string;
            }
            leaf external-vpn {
                type boolean;
            }
            leaf elan-tag {
                type uint32;
            }
    }

    notification subnet-deleted-from-vpn{
            description "subnet deleted from vpn";
            leaf subnet-id {
                type yang:uuid;
            }
            leaf subnet-ip {
                type string;
            }
            leaf vpn-name {
                type string;
            }
            leaf external-vpn {
                type boolean;
            }
            leaf elan-tag {
                type uint32;
            }
    }

    notification subnet-updated-in-vpn{
            description "subnet updated in vpn";
            leaf subnet-id {
                 type yang:uuid;
            }
            leaf subnet-ip {
                 type string;
            }
            leaf vpn-name {
                 type string;
            }
            leaf external-vpn {
                 type boolean;
            }
            leaf elan-tag {
                type uint32;
            }
    }

    notification port-added-to-subnet{
            description "port added to subnet";
            leaf subnet-id{
                type yang:uuid;
            }
            leaf subnet-ip{
                type string;
            }
            leaf port-id{
                type yang:uuid;
            }
            leaf elan-tag {
                type uint32;
            }
    }

    notification port-removed-from-subnet{
            description "port removed from subnet";
            leaf subnet-id{
                type yang:uuid;
            }
            leaf subnet-ip{
                type string;
            }
            leaf port-id{
                type yang:uuid;
            }
            leaf elan-tag {
                type uint32;
            }
    }

    notification router-associated-to-vpn {
            description "router association to vpn";
            leaf router-id{
                type yang:uuid;
            }
            leaf vpn-id{
                type yang:uuid;
            }
    }

    notification router-disassociated-from-vpn {
            description "router disassociation from vpn";
            leaf router-id{
                type yang:uuid;
            }
            leaf vpn-id{
                type yang:uuid;
            }
    }

}
