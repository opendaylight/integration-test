module ebgp {

  yang-version "1";

  // namespace
  namespace "urn:ericsson:params:xml:ns:yang:ebgp";

  prefix "ericsson-bgp";

  // import some basic inet types
  import ietf-inet-types { prefix inet; revision-date "2013-07-15"; }


  // meta
  organization
    "Ericsson Bangalore";

  contact
    "Ericsson Bangalore"; 

  description
    "BGP configuration model for Ericsson's implementation of
    Opendaylight L3VPN";

  revision "2015-09-01" {
  }



typedef layer_type
  {
         description
                   "This value represents the layer to which
                   a VRF entry belongs to in IP protocol.";

         type enumeration
         {
           enum LAYER_2
           {
             value "1";
             description "VRF belongs to Layer 2 of IP Protocol.";
           }

           enum LAYER_3
           {
             value "2";
             description "VRF belongs to Layer 3 of IP Protocol.";
           }
         }
    }


    typedef encap_type
    {
        description
           "Encapsulation types supported as per
           RFC 5512 - The BGP Encapsulation Subsequent
           Address Family Identifier (SAFI) and the
           BGP Tunnel Encapsulation Attribute";

        type enumeration
        {
            enum L2TPV3_OVER_IP
            {
              value "1";
              description "L2TPV3_OVER_IP";
            }

            enum GRE
            {
              value "2";
              description "GRE";
            }

            enum IP_IN_IP
            {
              value "7";
              description "IP_IN_IP";
            }

            enum VXLAN
            {
              value "8";
              description "VXLAN";
            }

            enum MPLS
            {
              value "10";
              description "MPLS";
            }
        }
    }


    typedef protocol_type
    {
        description
                "protocol type - used to know which route type is referred to";

        type enumeration
        {
            enum PROTOCOL_LU
            {
              value "1";
              description "PROTOCOL_LU";
            }

            enum PROTOCOL_L3VPN
            {
              value "2";
              description "PROTOCOL_L3VPN";
            }

            enum PROTOCOL_EVPN
            {
              value "3";
              description "PROTOCOL_EVPN";
            }

            enum PROTOCOL_ANY
            {
              value "4";
              description "PROTOCOL_ANY";
            }
        }
    }


    leaf type {

       description
       "The type of the VPN Instance.
       L3 indicates it is an L3VPN.
       L2 indicates it is EVPN";

       type enumeration {

         enum l3 {
           value "0";
           description “L3VPN";
         }

         enum l2 {
           value "1";
           description "EVPN";
         }
       }

       default "l3";
    }
 container bgp {
  config "true"; 
  container config-server {
    leaf host {
      type inet:ipv4-address;
      mandatory "true";
    }
    leaf port {
      type uint32;
      mandatory "true"; 
    } 
  }

  container as-id {
    leaf local-as {
      type uint32;
      mandatory "true";
    }
    leaf router-id {
      type inet:ipv4-address;
    }
    leaf stalepath-time {
      type uint32;
      default 360;
    }
    leaf announce-fbit {
      type boolean;
    }
  }

  container graceful-restart {
    leaf stalepath-time {
      type uint32;
      mandatory "true";
    }
  }

  container logging {
    leaf file {
      type string;
    }
    leaf level {
      type string;
    }
  }

  list neighbors { 
    key "address";
    leaf address {
      type inet:ipv4-address;
      mandatory "true";
    }
    leaf remote-as {
      type uint32;
      mandatory "true";
    }
    container ebgp-multihop {
      leaf nhops {
        type uint32;
      }
      leaf peer-ip {
        type leafref {
          path "/ericsson-bgp:bgp/neighbors/address";
        }
      }
    }
    container update-source {
      leaf source-ip {
        type inet:ipv4-address;
      }
      leaf peer-ip {
        type leafref {
          path "/ericsson-bgp:bgp/neighbors/address";
        }
      }
    }
    list address-families {
      key "afi safi";
      leaf afi {
        type uint32;
        mandatory "true";
      }
      leaf safi {
        type uint32;
        mandatory "true";
      }
      leaf peer-ip {
        type leafref {
          path "/ericsson-bgp:bgp/neighbors/address";
        }
      }
    } //addr-families
  } // neighbhors


  list networks {

    key "rd prefix-len";
    leaf rd {
      type string;
    }
    leaf prefix-len {
          type string;
    }
    leaf nexthop {
      type inet:ipv4-address;
      mandatory "false";
    }
    leaf label {
      type uint32;
      mandatory "false";
    }
    leaf protocolType{
      type protocol_type;
      mandatory "true";
    }
    leaf ethtag {
      type uint32;
      mandatory "false";
    }
    leaf esi {
      type string;
      mandatory "false";
    }
    leaf macaddress {
      type string;
      mandatory "true";
    }
    leaf encapType {
      type encap_type;
      mandatory "false";
    }
    leaf routermac {
      type string;
      mandatory "false";
    }
    leaf l3vni {
      type uint32;
      mandatory "false";
    }
  } // networks

  list vrfs {
    key "rd";
    leaf layerType {
      type layer_type;
      mandatory "true";
    }
    leaf rd {
      type string;
    }
    leaf-list import-rts {
      type string;
    }
    leaf-list export-rts {
      type string;
    }
  }
 } // bgp
}
