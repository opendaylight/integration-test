module cloud-servicechain-api {
    yang-version 1;
    namespace "urn:opendaylight:netvirt:cloud-servicechain:api";
    prefix "cloud-servicechain-api";

    import config { prefix config; revision-date 2013-04-05; }

    description
        "Service definition for cloudservicechain  project";

    revision "2015-12-11" {
        description
            "Initial revision";
    }

    identity cloud-servicechain-api {
        base "config:service-type";
        config:java-class "org.opendaylight.netvirt.cloudservicechain.api.ICloudServiceChain";
    }
}
