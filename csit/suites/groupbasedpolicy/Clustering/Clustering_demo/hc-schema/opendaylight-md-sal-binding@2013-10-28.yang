module opendaylight-md-sal-binding {
	yang-version 1;
    namespace "urn:opendaylight:params:xml:ns:yang:controller:md:sal:binding";
    prefix "md-sal-binding";

    import config { prefix config; revision-date 2013-04-05; }

    description
        "Service definition for Binding Aware MD-SAL.";

    revision "2013-10-28" {
        description
            "Initial revision";
    }

    identity binding-broker-osgi-registry {
        base "config:service-type";
        config:java-class "org.opendaylight.controller.sal.binding.api.BindingAwareBroker";
    }

    identity binding-data-broker {
        base "config:service-type";
        config:java-class "org.opendaylight.controller.sal.binding.api.data.DataProviderService";
    }

    identity binding-async-data-broker {
        base "config:service-type";
        config:java-class "org.opendaylight.controller.md.sal.binding.api.DataBroker";
        config:disable-osgi-service-registration;
    }

    identity binding-data-consumer-broker {
        base "config:service-type";
        config:java-class "org.opendaylight.controller.sal.binding.api.data.DataBrokerService";
    }

    identity binding-rpc-registry {
        base "config:service-type";
        config:java-class "org.opendaylight.controller.sal.binding.api.RpcProviderRegistry";
        config:disable-osgi-service-registration;
    }

    identity binding-notification-service {
        base "config:service-type";
        config:java-class "org.opendaylight.controller.sal.binding.api.NotificationProviderService";
        config:disable-osgi-service-registration;
    }

    identity binding-codec-tree-factory {
        base "config:service-type";
        config:java-class "org.opendaylight.yangtools.binding.data.codec.api.BindingCodecTreeFactory";
        config:disable-osgi-service-registration;
    }

    identity binding-normalized-node-serializer {
        base "config:service-type";
        config:java-class "org.opendaylight.yangtools.binding.data.codec.api.BindingNormalizedNodeSerializer";
        config:disable-osgi-service-registration;
    }

    identity binding-notification-subscription-service {
        base "config:service-type";
        config:java-class "org.opendaylight.controller.sal.binding.api.NotificationService";
        config:disable-osgi-service-registration;
    }

}
