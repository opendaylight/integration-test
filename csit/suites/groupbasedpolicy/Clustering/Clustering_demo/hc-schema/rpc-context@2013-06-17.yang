module rpc-context {
    yang-version 1;
    namespace "urn:ietf:params:xml:ns:yang:rpc-context";
    prefix "rpcx";

    organization "TBD";

    contact "TBD";

    description "";

    revision 2013-06-17 {
        description "Initial mock";
    }


    grouping rpc-context-ref {
        description "A reference to RPC context.";
        leaf context-instance {
            type instance-identifier;
            description "Pointer to the context. ";
        }
    }

    extension "rpc-context-instance" {
        description
            "Marks enclosing (parent) schema node as suitable RPC context.
             The argument is identity which is used to identify RPC context
             type.";
        argument "context-type";
    }
}
