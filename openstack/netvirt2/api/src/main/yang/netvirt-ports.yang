module netvirt-ports {
    yang-version 1;
    namespace "urn:opendaylight:netvirt:ports";
    prefix "ports";

    revision "2015-12-27" {
        description "Initial revision of netvirt ports definition";
    }

    import ietf-inet-types { prefix inet; revision-date 2013-07-15;}
    import ietf-yang-types { prefix yang; revision-date "2013-07-15";}
    import netvirt-common { prefix "common"; }


    identity port-type-base {
        description "Base port type";
    }

    identity port-type-l2-network {
        base port-type-base;
        description "port type l2-network";
    }

    identity port-type-router {
        base port-type-base;
        description "port type router";
    }

    identity port-type-router-interface-distributed {
        base port-type-base;
        description "port type router interface distributed";
    }

    identity port-type-router-gateway {
        base port-type-base;
        description "port type router gateway";
    }

    identity port-type-dhcp {
        base port-type-base;
        description "port type dhcp";
    }

    identity port-type-floating-ip {
        base port-type-base;
        description "port type floatingip";
    }

    identity port-type-compute-nova {
        base port-type-base;
        description "port type compute nova";
    }

    typedef port-type {
        type identityref {
            base port-type-base;
        }
        description "This type is used to refer to an port Type.";
    }

    identity port-binding-type-base {
        description "Base port-binding type";
    }

    identity port-binding-type-vlan {
        base port-binding-type-base;
        description "port-binding type vlan";
    }

    identity port-binding-type-vxlan {
        base port-binding-type-base;
        description "port-binding type vxlan";
    }

    typedef port-binding-type {
        type identityref {
            base port-binding-type-base;
        }
        description "The port binding is used to bind one port to another in a hierarchical.";
    }

    grouping end-point {
        uses common:base-attributes;

        leaf macaddr {
            type yang:mac-address;
            description "MAC address entry";
        }

        leaf-list ipaddrs {
            description "Mechanism used to bind ports.";
            type inet:ip-address;
        }
    }

    grouping parent-port-binding {
        description "Optional. Used to bind one port to another hierarchically.  For example, a port
                     binding may be used to support multiple containers in a single VM. In this model
                     each container could use a VLAN-based sub-port on a single tap port.";

        leaf type {
            description "How is this port bound to the other.  E.g., VLAN";
            type port-binding-type;
        }

        leaf id {
            description "Depends on binding type.  E.g., if the type is VLAN, this would be the VLAN ID";
            type string;
        }

        leaf parent-port {
            description "Must be the UUID of another port.";
            type yang:uuid;
        }
    }

    grouping port {
        uses common:base-attributes;
        uses common:admin-attributes;

        leaf port-type {
            type port-type;
            description "The type of port.";
        }

        leaf parent {
            type yang:uuid;
            description "The UUID of the object this port is a member of.  For example, if the type is
                         port-type-l2-network, this will be the UUID of the l2-network";
        }

        uses parent-port-binding;

        // TODO: Can we use a leafref for the device locator?
        leaf device-uuid {
            type yang:uuid;
            description "Reference to the the device for this port";
        }

        leaf device-locator-uuid {
            type yang:uuid;
            description "Reference to the the device locator for this port";
        }

        list end-points {

            key macaddr;

            uses end-point;
        }
    }

    container ports {
        list port {
            description "List of ports.  Each port entry contains both logical and physical information.";

            key uuid;
            uses port;
        }
    }
}
